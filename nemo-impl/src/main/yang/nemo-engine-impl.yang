/*
 * Copyright (c) 2015 Huawei, Inc. and others. All rights reserved.
 *
 * This program and the accompanying materials are made available under the
 * terms of the Eclipse Public License v1.0 which accompanies this distribution,
 * and is available at http://www.eclipse.org/legal/epl-v10.html
 */

module nemo-engine-impl {
    yang-version 1;

    namespace "urn:opendaylight:params:xml:ns:yang:nemo:engine:impl";
    prefix "nemo-engine-impl";

    import config { prefix config; revision-date 2013-04-05; }
    import opendaylight-md-sal-binding { prefix mdsal; revision-date 2013-10-28; }

    description
        "This module contains the base YANG definitions for
         NEMO engine implementation.";

    revision "2015-10-10" {
        description
            "Initial revision.";
    }

    identity nemo-engine-impl {
        base config:module-type;
        config:java-name-prefix NemoEngine;
    }

    augment "/config:modules/config:module/config:configuration" {
        case nemo-engine-impl {
            when "/config:modules/config:module/config:type = 'nemo-engine-impl'";

            container data-broker {
                uses config:service-ref {
                    refine type {
                        mandatory false;
                        config:required-identity mdsal:binding-async-data-broker;
                    }
                }
            }
            container rpc-registry {
                uses config:service-ref {
                    refine type {
                        mandatory true;
                        config:required-identity mdsal:binding-rpc-registry;
                    }
                }
            }
        }
    }
}
