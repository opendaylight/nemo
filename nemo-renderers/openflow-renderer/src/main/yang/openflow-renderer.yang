/*
 * Copyright (c) 2015 Huawei, Inc. and others. All rights reserved.
 *
 * This program and the accompanying materials are made available under the
 * terms of the Eclipse Public License v1.0 which accompanies this distribution,
 * and is available at http://www.eclipse.org/legal/epl-v10.html
 */

module openflow-renderer {
    yang-version 1;

    namespace "urn:opendaylight:params:xml:ns:yang:nemo:openflow:renderer";
    prefix "openflow-renderer";

    description
        "This module defines the NEMO Openflow renderer model.";

    revision "2015-10-10" {
        description
            "Initial revision.";
    }
}
