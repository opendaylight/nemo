/*
 * Copyright (c) 2015 Huawei, Inc. and others. All rights reserved.
 *
 * This program and the accompanying materials are made available under the
 * terms of the Eclipse Public License v1.0 which accompanies this distribution,
 * and is available at http://www.eclipse.org/legal/epl-v10.html
 */
 
module cli-execution-sequence {
    yang-version 1;
    namespace "urn:opendaylight:params:xml:ns:yang:cli:execution:sequence";
    prefix "cli-exec-seq";
	
    import nemo-common {prefix nemo-common;}
    import nemo-engine-common {prefix nemo-engine-common;}
    
    revision "2015-11-19" {
        description
            "Initial revision.";
    }
    container device-cli-sequences {
        list device-cli-sequence {
            key "device-id user-id";
            leaf device-id {
                description
                    "A unique ID for a physical device.";
                type nemo-engine-common:physical-node-id;
                mandatory true;
            }

			leaf user-id {
                description
                    "The user ID for the cli.";
                type nemo-common:user-id;
            }

            list cli-sequence {
                
                key "cli-num";
                leaf cli-num {
                    description
                        "sequence number for one command.";
                    type uint32;
                    mandatory true;
                }
                leaf cli-content {
                    description
                        "The content of the command line.";
                    type string;
                    mandatory true;
                }
                leaf expected-return{
                    description
                        "The expected return result for the command.
                        The string can be empty string.";
                    type string;
                    mandatory true;
                    
                }
                leaf timeout{
                    description
                        "The execution time out value for the command.
                        The Unit is millisecond.Different commands may have
                        different time out value requirement.";
                    type uint32;
                    units millisecond;
                    mandatory true;
                }
            }
        }
    }
}
