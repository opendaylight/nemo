/*
 * Copyright (c) 2015 Huawei, Inc. and others. All rights reserved.
 *
 * This program and the accompanying materials are made available under the
 * terms of the Eclipse Public License v1.0 which accompanies this distribution,
 * and is available at http://www.eclipse.org/legal/epl-v10.html
 */

module cli-renderer {
    yang-version 1;

    namespace "urn:opendaylight:params:xml:ns:yang:nemo:cli:renderer";
    prefix "cli-renderer";

    description
        "This module defines the NEMO CLI renderer model.";

    revision "2015-11-19" {
        description
            "Initial revision.";
    }
}
