/*
 * Copyright (c) 2015 Huawei, Inc. and others. All rights reserved.
 *
 * This program and the accompanying materials are made available under the
 * terms of the Eclipse Public License v1.0 which accompanies this distribution,
 * and is available at http://www.eclipse.org/legal/epl-v10.html
 */

module cli-renderer-impl {
    yang-version 1;

    namespace "urn:opendaylight:params:xml:ns:yang:nemo:cli:renderer:impl";
    prefix "cli-renderer-impl";

    import config { prefix config; revision-date 2013-04-05; }
    import opendaylight-md-sal-binding { prefix mdsal; revision-date 2013-10-28; }

    description
        "This module contains the base YANG definitions for
         NEMO CLI renderer implementation.";

    revision "2015-11-19" {
        description
            "Initial revision.";
    }

    identity cli-renderer-impl {
        base config:module-type;
        config:java-name-prefix CliRenderer;
    }

    augment "/config:modules/config:module/config:configuration" {
        case cli-renderer-impl {
            when "/config:modules/config:module/config:type = 'cli-renderer-impl'";

            container data-broker {
                uses config:service-ref {
                    refine type {
                        mandatory false;
                        config:required-identity mdsal:binding-async-data-broker;
                    }
                }
            }
            container rpc-registry {
                uses config:service-ref {
                    refine type {
                        mandatory true;
                        config:required-identity mdsal:binding-rpc-registry;
                    }
                }
            }
            container notification-service {
                uses config:service-ref {
                    refine type {
                        mandatory true;
                        config:required-identity mdsal:binding-notification-service;
                    }
                }
            }
        }
    }
}
